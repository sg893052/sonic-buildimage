module openconfig-bfd-ext_new {

  yang-version "1";

  // namespace
  namespace "http://openconfig.net/yang/bfd-ext";

  prefix "oc-bfd-ext";

  // import some basic types
  import openconfig-types { prefix "oc-types"; }
  import openconfig-interfaces { prefix "oc-if"; }
  import openconfig-inet-types { prefix "oc-inet"; }
  import openconfig-network-instance { prefix "oc-ni"; }
  import openconfig-bfd { prefix "oc-bfd"; }

  description
    "An OpenConfig model extension of Bi-Directional Forwarding Detection (BFD)
    configuration and operational state.";

  typedef bfd-session-type {
    type enumeration {
      enum CONFIGURED {
        description
          "The BFD session is Configured.";
      }
      enum DYNAMIC {
        description
          "The BFD session is ceated by an application trigger.";
      }
    }
    description
      "The type of the BFD session according to the system referred
      to by the context of the leaf.";
  }

  grouping bfd-config {
    description
      "Top-level per-interface configuration parameters for BFD.";

    leaf enabled {
      type boolean;
      description
        "When this leaf is set to true then the BFD session is enabled
        - if it is set to false, it is administratively disabled.";
    }

    leaf local-address {
      type oc-inet:ip-address;
      description
        "The source IP address to be used for BFD sessions over this
        interface.";
    }

    leaf desired-minimum-tx-interval {
      type uint32;
      units microseconds;
      description
        "The minimum interval between transmission of BFD control
        packets that the operator desires. This value is advertised to
        the peer, however the actual interval used is specified by
        taking the maximum of desired-minimum-tx-interval and the
        value of the remote required-minimum-receive interval value.
        This value is specified as an integer number of microseconds.";
    }

    leaf required-minimum-receive {
      type uint32;
      units microseconds;
      description
        "The minimum interval between received BFD control packets that
        this system should support. This value is advertised to the
        remote peer to indicate the maximum frequency (i.e., minimum
        inter-packet interval) between BFD control packets that is
        acceptable to the local system.";
    }

    leaf desired-minimum-echo-receive {
      type uint32;
      units microseconds;
      description
        "The minimum interval between received BFD control packets that
        the operator desires. This value is advertised to the remote peer 
        to indicate the maximum frequency (i.e., minimum inter-packet interval) 
        between BFD control packets that is acceptable to the local system.";
    }

    leaf detection-multiplier {
      type uint8 {
        range "1..max";
      }
      description
        "The number of packets that must be missed to declare this
        session as down. The detection interval for the BFD session
        is calculated by multiplying the value of the negotiated
        transmission interval by this value.";
    }

    leaf echo-active {
        type boolean;
        description
          "This leaf is set to true when echo mode is enabled between
          the local and remote system. When it is set to false, solely
          asynchronous mode is active.";
      }
  }

  grouping bfd-session-state-sessiondetails-common-ext {
    description
      "Common session details extension for a BFD session.";

    leaf session-type {
      type bfd-session-type;
      description
        "The type of the BFD session perceived by the local system.";    
    }

    leaf remote-multiplier {
      type uint32;
      description "Remote session detection multiplier";
    }

    leaf local-multiplier {
      type uint32;
      description "Remote session detection multiplier";
    }

    leaf negotiated-transmission-interval {
      description "Negotiated transmit interval";
      type uint32;
      units microseconds;
    }

    leaf negotiated-receive-interval {
      description "Negotiated receive interval";
      type uint32;
      units microseconds;
    }

    leaf last-up-time {
      type oc-types:timeticks64;
      description
        "The time of the last transition of the BFD session to UP
        state, expressed as the number of nanoseconds since the 
        Unix epoch.";
    }
  }

  grouping session-states {
    description
      "Common operational state parameters that may be re-used across
      multiple BFD session contexts.";

    uses oc-bfd:bfd-session-state-sessiondetails-common;
    uses bfd-session-state-sessiondetails-common-ext;
    uses oc-bfd:bfd-session-state-echo-common;
    uses oc-bfd:bfd-session-state-async-common;
  }

  grouping bfd-session-params {
    description
      "grouping of common session identifiers";
  
      leaf remote-address {
        type oc-inet:ip-address;
        description
        "The IP address used by the remote system for this BFD session.";
      }

      leaf interface {
        type leafref {
          path "/oc-if:interfaces/" +
            "oc-if:interface/oc-if:config/oc-if:name";
        }
        description "Interface to use to contact peer";
      }

      leaf vrf {
        type leafref {
          path "/oc-ni:network-instances/" +
            "oc-ni:network-instance/oc-ni:config/oc-ni:name";
        }
        description "Virtual Routing Domain name";
      }
  }

  container bfd {
    description
      "Configuration and operational state parameters for BFD.";
    reference "RFC5880, RFC5881";
    container sessions {
      list single-hop {
        key "remote-address interface vrf";
        description "List of single hop sessions";

        uses bfd-session-params;

        uses bfd-config;
        container stats {
          uses session-states;
          config false;
        }
      }

      list multi-hop {
        key "local-address remote-address interface vrf";
        description "List of multi hop sessions";

        uses bfd-session-params;
      
        uses bfd-config;
        container stats {
          uses session-states;
          config false;
        }
      }
    }
  }

  deviation /oc-bfd:bfd {
        deviate not-supported;
    }

  deviation /oc-bfd:echo/oc-bfd:last-packet-transmitted {
        deviate not-supported;
    }
}
