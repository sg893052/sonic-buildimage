module openconfig-udld-ext {

  yang-version "1";

  // namespace
  namespace "http://openconfig.net/yang/udld/extension";

  prefix "oc-udld-ext";

  import openconfig-interfaces { prefix oc-if; }
  import ietf-yang-types { prefix yang; }
  import openconfig-extensions { prefix oc-ext; }
  import openconfig-udld-types { prefix oc-udld-types; }


  // meta
  organization "OpenConfig working group";

  contact
    "OpenConfig working group
    www.openconfig.net";

  description
    "This module defines configuration and operational state data
    for the UDLD protocol.";

  oc-ext:openconfig-version "0.1.0";

  revision "2020-05-04" {
    description
      "Initial public revision";
    reference "0.1.0";
  }

  // OpenConfig specific extensions for module metadata.
  oc-ext:regexp-posix;
  oc-ext:catalog-organization "openconfig";
  oc-ext:origin "openconfig";

  // identity statements


  // grouping statements

  grouping udld-interface-counters {
    description
      "Definition of global and per-interface counters";

    leaf frame-out {
      type yang:counter64;
      default 0;
      description
        "The number of frames transmitted out.";
    }

    leaf frame-in {
      type yang:counter64;
      default 0;
      description
        "The number of udld frames received.";
    }

    leaf frame-error-in {
      type yang:counter64;
      default 0;
      description
        "The number of UDLD frames received with errors.";
    }

  }


  grouping udld-common-config {
    description
      "Groups UDLD enable and mode config common to both Global and interface level";

    leaf admin-enable {
        type boolean;
        default false;
        description
            "Enable/Disable UDLD";
    }

    leaf aggressive {
        type boolean;
        default false;
        description
            "Enable/Disable aggressive mode of UDLD";
    }
  }


  grouping udld-interface-config {
    description
      "Configuration data for UDLD on each interface";

    leaf name {
      type oc-if:base-interface-ref;
      description
        "Reference to the UDLD Ethernet interface";
    }
    uses udld-common-config;
  }

  grouping udld-interface-info-common {
	leaf device-id {
		type string;
		description
			"device id(MAC)";
	}

	leaf device-name {
		type string;
		description
			"device name";
	}

    leaf status {
        type identityref {
          base oc-udld-types:UDLD_PORT_STATUS;
        }
        description
            "UDLD port status";
    }
  }


  grouping udld-interface-state {
    description
      "Operational state data for UDLD on each interface";

    container local-info {
      uses udld-interface-info-common;
    }
    container neighbors-info {
      list neighbor {
        key "ifname index";

        leaf ifname {
            type oc-if:base-interface-ref;
            description
                "Reference of local port on which UDLD is configured.";
        }

        leaf index {
            type uint16;
            default 0;
            description
                "Index number of neighbor port";
        }

        uses udld-interface-info-common;
      }
    }

    container counters {
      description
        "UDLD counters on each interface";

      uses udld-interface-counters;
    }
  }


  grouping udld-interface-top {
    description
      "Top-level grouping ";

    container interfaces {
      description
        "Enclosing container ";

      list interface {
        key "name";
        description
          "List of interfaces on which UDLD is enabled / available";

        leaf name {
          type leafref {
            path "../config/name";
          }
          description
            "Reference to the UDLD Ethernet interface";
        }

        container config {
          description
            "Configuration data for UDLD on each interface";

          uses udld-interface-config;
        }

        container state {

          config false;

          description
            "Operational state data ";

          uses udld-interface-config;
          uses udld-interface-state;
        }

      }
    }
  }


  grouping udld-global-config {
    description
      "Configuration data for global UDLD parameters";

    uses udld-common-config;

    leaf msg-time {
        type uint8 {
            range "1..30" {
                error-message "Invalid UDLD message time value.";
            }
        }
        units seconds;
        default 1;
        description
            "It is the time interval at which periodic hellos are
            exchanged. Default is 1 second";
    }

    leaf multiplier {
        type uint8 {
            range "3..10" {
                error-message "Invalid UDLD multiplier value.";
            }
        }
        default 3;
        description
            "This multiplier value is used to determine the timeout
            interval (i.e. message-time x multiplier value) after
            which UDLD declares the state of the link.";
    }

  }


  grouping udld-top {
    description
      "Top-level grouping for UDLD model";

    container udld {
      description
        "Top-level container for UDLD configuration and state data";

      container config {
        description
          "Configuration data ";

        uses udld-global-config;
      }

      container state {

        config false;

        description
          "Operational state data for UDLD";

        uses udld-global-config;
      }

      uses udld-interface-top;
    }
  }

  // data definition statements

  uses udld-top;

}
